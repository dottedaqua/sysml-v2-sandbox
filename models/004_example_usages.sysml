package example004 {
    part p1 {
        item i1;
        action a1;
        action a2;
        exhibit state stateMachine {
            entry;
            then perform a1;
            then perform a2;
            then a1;
            then a2;            
            then done;
        }
    }
} // package example004

//
Package example004 (585fc402-7f57-4583-a501-11b46c1053f6)
  [OwningMembership] PartUsage p1 (c97af800-6dbe-4266-aa30-0b22fe646e1f)
    [Subsetting (implicit)] PartUsage parts (0c6a9942-4bb9-58da-8344-57ecd220d4de)
    [FeatureMembership] ItemUsage i1 (5f615a87-bdde-4546-98a7-44975c869ec2)
      [Subsetting (implicit)] ItemUsage subitems (f6f04e9e-c8f9-5a8e-8e4b-a4504ca2bf85)
      [OwningMembership] Multiplicity (868ea3ef-060b-406b-822b-c35b3d889b61)
        [Subsetting (implicit)] MultiplicityRange exactlyOne (64e18b84-0e05-5c95-a003-c0f60a269893)
    [FeatureMembership] PerformActionUsage a1 (26365c9d-66ac-4e03-b640-aa9773a18bd3)
      [Subsetting (implicit)] ActionUsage performedActions (0856ed9f-5115-58b3-a51f-ba54aca3dce5)
    [FeatureMembership] PerformActionUsage a2 (c18f96c8-28cf-42c4-a0b5-6aa4d33f3531)
      [Subsetting (implicit)] ActionUsage performedActions (0856ed9f-5115-58b3-a51f-ba54aca3dce5)
    [FeatureMembership] ExhibitStateUsage stateMachine (a111f709-ef26-42e8-ae15-a1e21ff9dc91)
      [Subsetting (implicit)] StateUsage exhibitedStates (4e03b9fa-285a-54dd-8378-40c5e90d0e00)
      [StateSubactionMembership] ActionUsage entryAction (4bca8a85-7ee4-4915-8834-021719f2c431)
        [Redefinition (implicit)] PerformActionUsage entryAction (683a0ec4-7bdc-58e5-883b-ec7f4f1963d6)
        [Subsetting (implicit)] Step subperformances (e00899ec-5d00-5a31-9690-3791a3dbbe2e)
      [FeatureMembership] SuccessionAsUsage (5919b630-f31c-4116-93bb-c329c48494c9)
        [Subsetting (implicit)] Feature happensBeforeLinks (0e1bba0a-81f0-518c-8415-d1976bd38f8d)
        [EndFeatureMembership] ReferenceUsage earlierOccurrence (fb3b4c57-328e-4e3b-b6e5-3b541d79ac1b)
          [Redefinition (implicit)] Feature earlierOccurrence (7d7065b6-1bb8-5bb5-b421-cc92f2e84584)
          [ReferenceSubsetting (implicit)] ActionUsage entryAction (4bca8a85-7ee4-4915-8834-021719f2c431)
          [OwningMembership] Multiplicity (ac6a4789-e62c-46b4-be29-98871af4e883)
            [Subsetting (implicit)] MultiplicityRange exactlyOne (64e18b84-0e05-5c95-a003-c0f60a269893)
        [EndFeatureMembership] ReferenceUsage laterOccurrence (ed2d98fa-f34e-40dd-83a4-c134d22e80c7)
          [Redefinition (implicit)] Feature laterOccurrence (99bd4b60-e5a9-55fb-8cea-1dcf517e50ec)
          [ReferenceSubsetting (implicit)] PerformActionUsage a1 (62e331b0-29ec-4e8c-aab7-b3f0a95fd757)
          [OwningMembership] Multiplicity (15ccbe2e-e445-4e4f-9404-614f4d0ab534)
            [Subsetting (implicit)] MultiplicityRange exactlyOne (64e18b84-0e05-5c95-a003-c0f60a269893)
      [FeatureMembership] PerformActionUsage a1 (62e331b0-29ec-4e8c-aab7-b3f0a95fd757)
        [Subsetting (implicit)] Step enclosedPerformances (d2f2efc4-b3fe-5807-85bc-416fbebb05f0)
        [ReferenceSubsetting] PerformActionUsage a1 (26365c9d-66ac-4e03-b640-aa9773a18bd3)
      [FeatureMembership] SuccessionAsUsage (a6b1834d-ba01-40c3-a115-ed4b878e6e0f)
        [Subsetting (implicit)] Feature happensBeforeLinks (0e1bba0a-81f0-518c-8415-d1976bd38f8d)
        [EndFeatureMembership] ReferenceUsage earlierOccurrence (a2200da0-74ac-44f5-b4b5-a1ffa55c810c)
          [Redefinition (implicit)] Feature earlierOccurrence (7d7065b6-1bb8-5bb5-b421-cc92f2e84584)
          [ReferenceSubsetting (implicit)] PerformActionUsage a1 (62e331b0-29ec-4e8c-aab7-b3f0a95fd757)
          [OwningMembership] Multiplicity (7357a1ec-2dd2-4cf1-8e46-47a7f04a693b)
            [Subsetting (implicit)] MultiplicityRange exactlyOne (64e18b84-0e05-5c95-a003-c0f60a269893)
        [EndFeatureMembership] ReferenceUsage laterOccurrence (593b1747-998a-43f3-b57c-c96842d43f38)
          [Redefinition (implicit)] Feature laterOccurrence (99bd4b60-e5a9-55fb-8cea-1dcf517e50ec)
          [ReferenceSubsetting (implicit)] PerformActionUsage a2 (f6c953f6-c519-4de1-a657-4ec3d0b7f817)
          [OwningMembership] Multiplicity (076e57ee-1dd0-443f-b2a1-9c4c6011c4db)
            [Subsetting (implicit)] MultiplicityRange exactlyOne (64e18b84-0e05-5c95-a003-c0f60a269893)
      [FeatureMembership] PerformActionUsage a2 (f6c953f6-c519-4de1-a657-4ec3d0b7f817)
        [Subsetting (implicit)] Step enclosedPerformances (d2f2efc4-b3fe-5807-85bc-416fbebb05f0)
        [ReferenceSubsetting] PerformActionUsage a2 (c18f96c8-28cf-42c4-a0b5-6aa4d33f3531)
      [FeatureMembership] TransitionUsage (72c1600d-da8c-4a2a-a8d5-ad96ec41439a)
        [Subsetting (implicit)] ActionUsage decisionTransitions (384046fe-8dea-5263-bce6-36dd9a023111)
        [Membership] PerformActionUsage a2 (f6c953f6-c519-4de1-a657-4ec3d0b7f817)
        [ParameterMembership] ReferenceUsage transitionLinkSource (da59d13c-7693-4ae2-93f0-fbd37ef9e531)
          [Redefinition (implicit)] ReferenceUsage transitionLinkSource (79252dcf-845e-5151-a0e9-28ee09987171)
        [OwningMembership] SuccessionAsUsage (22531ac4-6479-46cf-94aa-b804d2350416)
          [Subsetting (implicit)] Feature happensBeforeLinks (0e1bba0a-81f0-518c-8415-d1976bd38f8d)
          [EndFeatureMembership] ReferenceUsage earlierOccurrence (51c16a26-9dfd-440d-b3e2-88f83e835e01)
            [Redefinition (implicit)] Feature earlierOccurrence (7d7065b6-1bb8-5bb5-b421-cc92f2e84584)
            [ReferenceSubsetting (implicit)] PerformActionUsage a2 (f6c953f6-c519-4de1-a657-4ec3d0b7f817)
            [OwningMembership] Multiplicity (ebe303eb-75fb-40b2-9f8b-b1f5f0e8d59a)
              [Subsetting (implicit)] MultiplicityRange exactlyOne (64e18b84-0e05-5c95-a003-c0f60a269893)
          [EndFeatureMembership] ReferenceUsage laterOccurrence (6b2de623-1b6b-49d2-9c15-e10baa8ef725)
            [Redefinition (implicit)] Feature laterOccurrence (99bd4b60-e5a9-55fb-8cea-1dcf517e50ec)
            [ReferenceSubsetting] PerformActionUsage a1 (62e331b0-29ec-4e8c-aab7-b3f0a95fd757)
            [OwningMembership] Multiplicity (86fa5d92-2d76-4c89-8abb-a5e564a7022a)
              [Subsetting (implicit)] MultiplicityRange exactlyOne (64e18b84-0e05-5c95-a003-c0f60a269893)
        [FeatureMembership] ReferenceUsage transitionLink (aac2f6ac-d23e-49d3-ba80-b17a069f2181)
          [Redefinition (implicit)] Feature transitionLink (88fcc394-fccf-51de-a229-138dee74449e)
      [FeatureMembership] TransitionUsage (9df6a518-86cb-4826-944d-24cabb9851f3)
        [Subsetting (implicit)] ActionUsage decisionTransitions (384046fe-8dea-5263-bce6-36dd9a023111)
        [Membership] PerformActionUsage a2 (f6c953f6-c519-4de1-a657-4ec3d0b7f817)
        [ParameterMembership] ReferenceUsage transitionLinkSource (13b5c08a-865a-4114-bcbb-f932a0597b34)
          [Redefinition (implicit)] ReferenceUsage transitionLinkSource (79252dcf-845e-5151-a0e9-28ee09987171)
        [OwningMembership] SuccessionAsUsage (21da4bf2-5b11-4386-8825-d5246d6a5a2c)
          [Subsetting (implicit)] Feature happensBeforeLinks (0e1bba0a-81f0-518c-8415-d1976bd38f8d)
          [EndFeatureMembership] ReferenceUsage earlierOccurrence (ef93d7f8-de07-4778-92b4-f2d17f14a49e)
            [Redefinition (implicit)] Feature earlierOccurrence (7d7065b6-1bb8-5bb5-b421-cc92f2e84584)
            [ReferenceSubsetting (implicit)] PerformActionUsage a2 (f6c953f6-c519-4de1-a657-4ec3d0b7f817)
            [OwningMembership] Multiplicity (4136c614-11a0-4573-aae8-7bf8bcfacb50)
              [Subsetting (implicit)] MultiplicityRange exactlyOne (64e18b84-0e05-5c95-a003-c0f60a269893)
          [EndFeatureMembership] ReferenceUsage laterOccurrence (008aca1d-b8c9-42c3-8562-d66177722273)
            [Redefinition (implicit)] Feature laterOccurrence (99bd4b60-e5a9-55fb-8cea-1dcf517e50ec)
            [ReferenceSubsetting] PerformActionUsage a2 (f6c953f6-c519-4de1-a657-4ec3d0b7f817)
            [OwningMembership] Multiplicity (91ee4e91-8d3d-4871-9d38-3d273105151e)
              [Subsetting (implicit)] MultiplicityRange exactlyOne (64e18b84-0e05-5c95-a003-c0f60a269893)
        [FeatureMembership] ReferenceUsage transitionLink (ad516050-ad95-4f7b-bee1-e32c10185bc3)
          [Redefinition (implicit)] Feature transitionLink (88fcc394-fccf-51de-a229-138dee74449e)
      [FeatureMembership] TransitionUsage (a396fdd0-811b-4865-aa05-94da15b38245)
        [Subsetting (implicit)] ActionUsage decisionTransitions (384046fe-8dea-5263-bce6-36dd9a023111)
        [Membership] PerformActionUsage a2 (f6c953f6-c519-4de1-a657-4ec3d0b7f817)
        [ParameterMembership] ReferenceUsage transitionLinkSource (1f27c972-169c-4eec-9e22-63d02c7e7196)
          [Redefinition (implicit)] ReferenceUsage transitionLinkSource (79252dcf-845e-5151-a0e9-28ee09987171)
        [OwningMembership] SuccessionAsUsage (294be878-188d-4bf2-953e-54c6c8631f92)
          [Subsetting (implicit)] Feature happensBeforeLinks (0e1bba0a-81f0-518c-8415-d1976bd38f8d)
          [EndFeatureMembership] ReferenceUsage earlierOccurrence (de898e29-526e-4c26-a24e-6152709b74a3)
            [Redefinition (implicit)] Feature earlierOccurrence (7d7065b6-1bb8-5bb5-b421-cc92f2e84584)
            [ReferenceSubsetting (implicit)] PerformActionUsage a2 (f6c953f6-c519-4de1-a657-4ec3d0b7f817)
            [OwningMembership] Multiplicity (c1951fd7-7392-4af1-a561-7338385448dc)
              [Subsetting (implicit)] MultiplicityRange exactlyOne (64e18b84-0e05-5c95-a003-c0f60a269893)
          [EndFeatureMembership] ReferenceUsage laterOccurrence (29d8ed9a-6f88-481e-8469-a837fad15dac)
            [Redefinition (implicit)] Feature laterOccurrence (99bd4b60-e5a9-55fb-8cea-1dcf517e50ec)
            [ReferenceSubsetting] StateUsage done (c2229489-0c87-571f-806a-29ce5013452f)
            [OwningMembership] Multiplicity (0dc65b29-4f57-4784-9cc6-215318c8d0ed)
              [Subsetting (implicit)] MultiplicityRange exactlyOne (64e18b84-0e05-5c95-a003-c0f60a269893)
        [FeatureMembership] ReferenceUsage transitionLink (0060ada8-ae82-4388-87dc-7ee9fb2852be)
          [Redefinition (implicit)] Feature transitionLink (88fcc394-fccf-51de-a229-138dee74449e)
