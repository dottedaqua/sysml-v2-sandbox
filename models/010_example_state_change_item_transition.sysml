package example010 {
    package defs {
        item def I1;
        item def iAnything;
        item def StateTransitionTrigger;
        action def A1 {
            out item iout : I1;
        }
        action def A2 {
            in item iin : I1;
            out item iout : iAnything;
        }
        action def A3 {
            in item iin : iAnything;
        }
    } // package defs

    part p1 {
        action a1 : defs::A1;
        action a2 : defs::A2;
        action a3 : defs::A3;
        flow from a2.iout to a3.iin;

        // port required for "via"
        exhibit state stateMachine {
            entry;
            then state s1 {
                do action s1Do {
                    perform a1;
                    then send a1.iout to p1;
                    then send new defs::StateTransitionTrigger() to p1;
                    then done;
                }
            }
            accept defs::StateTransitionTrigger via p1 then s2; // Accepts the item from p1 and transitions to state s2
            state s2 {
                do action s2Do {
                    action getDataFromS1 accept iFromS1 : defs::I1;
                    flow from getDataFromS1.iFromS1 to a2.iin;
                    first getDataFromS1;
                    then perform a2;
                    then perform a3;
                    then done;
                }
            }
            then done;
        }
    }
} // package example010

/* /Package example010 (7aa4f922-687d-438a-a176-c3da627496d3)
 * [OwningMembership] Package defs (8e8ea4b8-e4d9-4ecf-bcb5-8690ee562e08)
 *   [OwningMembership] ItemDefinition I1 (f34d6b5b-010a-4d9f-8a4a-f4f2529d1815)
 *     [Subclassification (implicit)] ItemDefinition Item (8e9bd20f-ea8f-5a87-9759-f196d58bdd1a)
 *   [OwningMembership] ItemDefinition iAnything (08f11e92-5b2b-4513-b0e0-b6a2f9f75137)
 *     [Subclassification (implicit)] ItemDefinition Item (8e9bd20f-ea8f-5a87-9759-f196d58bdd1a)
 *   [OwningMembership] ItemDefinition StateTransitionTrigger (bc4fa98a-3d9f-46b4-bfd3-975a27e7e852)
 *     [Subclassification (implicit)] ItemDefinition Item (8e9bd20f-ea8f-5a87-9759-f196d58bdd1a)
 *   [OwningMembership] ActionDefinition A1 (00708adc-ecd4-47c9-a4d9-1be655bf4d30)
 *     [Subclassification (implicit)] ActionDefinition Action (6e44fcc3-4ac4-5e93-a695-61791fa23309)
 *     [FeatureMembership] ItemUsage iout (4ab86573-5eca-4877-9162-1ef487537e2f)
 *       [Subsetting (implicit)] ItemUsage items (b46000ca-4408-5855-9a4f-3957162cb899)
 *       [FeatureTyping] ItemDefinition I1 (f34d6b5b-010a-4d9f-8a4a-f4f2529d1815)
 *       [OwningMembership] Multiplicity (5022ab1a-4d4b-41d3-890d-62543173b2f3)
 *         [Subsetting (implicit)] MultiplicityRange exactlyOne (64e18b84-0e05-5c95-a003-c0f60a269893)
 *   [OwningMembership] ActionDefinition A2 (a7f15ffa-1e2a-45a4-a3b9-830b8b46e8e4)
 *     [Subclassification (implicit)] ActionDefinition Action (6e44fcc3-4ac4-5e93-a695-61791fa23309)
 *     [FeatureMembership] ItemUsage iin (b02e5d3f-91e0-4ec6-9141-de64d689e10a)
 *       [Subsetting (implicit)] ItemUsage items (b46000ca-4408-5855-9a4f-3957162cb899)
 *       [FeatureTyping] ItemDefinition I1 (f34d6b5b-010a-4d9f-8a4a-f4f2529d1815)
 *       [OwningMembership] Multiplicity (14381361-09de-4aa5-8e9a-7558a8787483)
 *         [Subsetting (implicit)] MultiplicityRange exactlyOne (64e18b84-0e05-5c95-a003-c0f60a269893)
 *     [FeatureMembership] ItemUsage iout (7a190673-af87-4349-b061-536f75a1cd49)
 *       [Subsetting (implicit)] ItemUsage items (b46000ca-4408-5855-9a4f-3957162cb899)
 *       [FeatureTyping] ItemDefinition iAnything (08f11e92-5b2b-4513-b0e0-b6a2f9f75137)
 *       [OwningMembership] Multiplicity (53bda809-8990-4bbc-b8ef-95c93aaa6aed)
 *         [Subsetting (implicit)] MultiplicityRange exactlyOne (64e18b84-0e05-5c95-a003-c0f60a269893)
 *   [OwningMembership] ActionDefinition A3 (6050f1e3-3f2c-4121-a7c7-f471ec278b23)
 *     [Subclassification (implicit)] ActionDefinition Action (6e44fcc3-4ac4-5e93-a695-61791fa23309)
 *     [FeatureMembership] ItemUsage iin (75a002e3-994b-4f5b-8bc0-10aace87942e)
 *       [Subsetting (implicit)] ItemUsage items (b46000ca-4408-5855-9a4f-3957162cb899)
 *       [FeatureTyping] ItemDefinition iAnything (08f11e92-5b2b-4513-b0e0-b6a2f9f75137)
 *       [OwningMembership] Multiplicity (26bf3b37-2c50-41af-beb0-a0e0ba2cc047)
 *         [Subsetting (implicit)] MultiplicityRange exactlyOne (64e18b84-0e05-5c95-a003-c0f60a269893)
 * [OwningMembership] PartUsage p1 (9c52c7b1-5b21-4345-a2f1-037163c68574)
 *   [Subsetting (implicit)] PartUsage parts (0c6a9942-4bb9-58da-8344-57ecd220d4de)
 *   [FeatureMembership] PerformActionUsage a1 (0d67397a-24df-4e70-b3b0-e75372ac105a)
 *     [Subsetting (implicit)] ActionUsage performedActions (0856ed9f-5115-58b3-a51f-ba54aca3dce5)
 *     [FeatureTyping] ActionDefinition A1 (00708adc-ecd4-47c9-a4d9-1be655bf4d30)
 *   [FeatureMembership] PerformActionUsage a2 (96d92c9c-ee8b-4ab5-b32c-f771c5e3f5ab)
 *     [Subsetting (implicit)] ActionUsage performedActions (0856ed9f-5115-58b3-a51f-ba54aca3dce5)
 *     [FeatureTyping] ActionDefinition A2 (a7f15ffa-1e2a-45a4-a3b9-830b8b46e8e4)
 *   [FeatureMembership] PerformActionUsage a3 (fdf2cda8-560b-49f2-bbe9-df838c082f10)
 *     [Subsetting (implicit)] ActionUsage performedActions (0856ed9f-5115-58b3-a51f-ba54aca3dce5)
 *     [FeatureTyping] ActionDefinition A3 (6050f1e3-3f2c-4121-a7c7-f471ec278b23)
 *   [FeatureMembership] FlowUsage (257fa873-0d42-4d35-9483-5e9ec48693d6)
 *     [Subsetting (implicit)] FlowUsage flows (58f4b8ef-ef56-5e97-8def-549155818a37)
 *     [Subsetting (implicit)] ActionUsage ownedActions (bfd5fb0e-e87b-51ea-a438-6a93d18b05a1)
 *     [EndFeatureMembership] FlowEnd source (ccde73d4-91ff-4702-914e-0c9c5660b74c)
 *       [Redefinition (implicit)] OccurrenceUsage source (9d174cd9-1d36-52f0-9c44-62001ffb9568)
 *       [ReferenceSubsetting] PerformActionUsage a2 (96d92c9c-ee8b-4ab5-b32c-f771c5e3f5ab)
 *       [FeatureMembership] ReferenceUsage iout (43eabbe3-e311-4e50-9dc4-c887276a957d)
 *         [Redefinition (implicit)] Feature sourceOutput (b0828d4d-ca40-572c-8276-734daa226ea6)
 *         [Redefinition] ItemUsage iout (7a190673-af87-4349-b061-536f75a1cd49)
 *     [EndFeatureMembership] FlowEnd target (b598ab38-f829-448a-80c5-81da07caa94e)
 *       [Redefinition (implicit)] OccurrenceUsage target (bf43c516-b2fd-59b0-ae53-a534f1289406)
 *       [ReferenceSubsetting] PerformActionUsage a3 (fdf2cda8-560b-49f2-bbe9-df838c082f10)
 *       [FeatureMembership] ReferenceUsage iin (a33f7b1c-fb3d-4796-99d1-d8481e2caef6)
 *         [Redefinition (implicit)] Feature targetInput (23f50cb6-e79a-5ea6-ab6f-6402cf94870b)
 *         [Redefinition] ItemUsage iin (75a002e3-994b-4f5b-8bc0-10aace87942e)
 *   [FeatureMembership] ExhibitStateUsage stateMachine (09c6c16e-a2f7-4fc3-b3c5-56456fdebd1c)
 *     [Subsetting (implicit)] StateUsage exhibitedStates (4e03b9fa-285a-54dd-8378-40c5e90d0e00)
 *     [StateSubactionMembership] ActionUsage entryAction (4ae854d2-e8d0-4d5a-9294-dc9a200a6277)
 *       [Redefinition (implicit)] PerformActionUsage entryAction (683a0ec4-7bdc-58e5-883b-ec7f4f1963d6)
 *       [Subsetting (implicit)] Step subperformances (e00899ec-5d00-5a31-9690-3791a3dbbe2e)
 *     [FeatureMembership] SuccessionAsUsage (e55605ff-22cc-42a4-b4eb-1d20daf3e5f9)
 *       [Subsetting (implicit)] Feature happensBeforeLinks (0e1bba0a-81f0-518c-8415-d1976bd38f8d)
 *       [EndFeatureMembership] ReferenceUsage earlierOccurrence (6b58bdb4-400c-4c57-a2f0-4e531633b84f)
 *         [Redefinition (implicit)] Feature earlierOccurrence (7d7065b6-1bb8-5bb5-b421-cc92f2e84584)
 *         [ReferenceSubsetting (implicit)] ActionUsage entryAction (4ae854d2-e8d0-4d5a-9294-dc9a200a6277)
 *         [OwningMembership] Multiplicity (09ad3e79-719c-44d1-9a31-892d959c56d7)
 *           [Subsetting (implicit)] MultiplicityRange exactlyOne (64e18b84-0e05-5c95-a003-c0f60a269893)
 *       [EndFeatureMembership] ReferenceUsage laterOccurrence (9a9a985e-05f5-4816-ae15-4c2561570a90)
 *         [Redefinition (implicit)] Feature laterOccurrence (99bd4b60-e5a9-55fb-8cea-1dcf517e50ec)
 *         [ReferenceSubsetting (implicit)] StateUsage s1 (f39cbdc7-d20a-4ac3-9a31-cea2db848e76)
 *         [OwningMembership] Multiplicity (16500a7b-49cd-49e0-bf13-4de22390daed)
 *           [Subsetting (implicit)] MultiplicityRange exactlyOne (64e18b84-0e05-5c95-a003-c0f60a269893)
 *     [FeatureMembership] StateUsage s1 (f39cbdc7-d20a-4ac3-9a31-cea2db848e76)
 *       [Subsetting (implicit)] StateUsage exclusiveStates (127c2ef2-9f87-52f2-93f6-5f7acbbdb70b)
 *       [StateSubactionMembership] PerformActionUsage s1Do (b06792ff-0975-46de-a29e-f098453ea911)
 *         [Redefinition (implicit)] PerformActionUsage doAction (be1e82ae-d5b8-53cf-8ae6-092905daf358)
 *         [FeatureMembership] PerformActionUsage a1 (2a175b67-1163-4f3f-8b5e-91f6a14ae6ae)
 *           [Subsetting (implicit)] Step enclosedPerformances (d2f2efc4-b3fe-5807-85bc-416fbebb05f0)
 *           [ReferenceSubsetting] PerformActionUsage a1 (0d67397a-24df-4e70-b3b0-e75372ac105a)
 *         [FeatureMembership] SendActionUsage (4c473ca1-694d-4212-b73e-e94cfc596b0a)
 *           [Subsetting (implicit)] ActionUsage sendSubactions (3e0dc934-f25c-5dea-988f-15724c029d88)
 *           [ParameterMembership] ReferenceUsage payload (dcf8c470-6310-41c1-9703-1bbb01ef3d2e)
 *             [Redefinition (implicit)] ReferenceUsage payload (a8558e47-1012-5952-a726-cc6f69e02b9e)
 *             [FeatureValue] FeatureChainExpression . (ca25c3af-5419-4fab-89fd-1639e170d09c)
 *               [ReturnParameterMembership] Feature result (45dce2dd-faeb-4b8c-93b6-9ca2584b1282)
 *           [ParameterMembership] ReferenceUsage sender (06414b55-f651-46c5-925b-d1261385bdb9)
 *             [Redefinition (implicit)] Feature sender (e96dffdb-38dc-54a1-9129-78e6126445c2)
 *           [ParameterMembership] ReferenceUsage receiver (df5c8ea3-b772-4da1-acae-7c8bdb9860b7)
 *             [Redefinition (implicit)] Feature receiver (712809ae-d7b1-5109-ba8c-dd121e343210)
 *             [FeatureValue] FeatureReferenceExpression p1 (7b724f3a-43e4-4fdb-99e1-4a7c7b53f43b)
 *               [ReturnParameterMembership] Feature result (c6f02a88-6556-4934-9a41-e9577e80cce2)
 *         [FeatureMembership] SendActionUsage (7b3d948b-163d-48a8-9245-162a3326c592)
 *           [Subsetting (implicit)] ActionUsage sendSubactions (3e0dc934-f25c-5dea-988f-15724c029d88)
 *           [ParameterMembership] ReferenceUsage payload (f4aeee1c-e53f-4e68-9779-163ddc70a3a3)
 *             [Redefinition (implicit)] ReferenceUsage payload (a8558e47-1012-5952-a726-cc6f69e02b9e)
 *             [FeatureValue] ConstructorExpression (12f124d8-578d-4cbd-befb-e154331e9cc7)
 *               [ReturnParameterMembership] Feature result (a10a0d70-490b-4919-a364-fc6c176a01a4)
 *           [ParameterMembership] ReferenceUsage sender (89374bf5-4b5c-48c4-8e09-fd5d43f9f91b)
 *             [Redefinition (implicit)] Feature sender (e96dffdb-38dc-54a1-9129-78e6126445c2)
 *           [ParameterMembership] ReferenceUsage receiver (d9e52b67-e01c-4e60-8619-d9d31a8f8587)
 *             [Redefinition (implicit)] Feature receiver (712809ae-d7b1-5109-ba8c-dd121e343210)
 *             [FeatureValue] FeatureReferenceExpression p1 (27c9771e-bce6-49a9-9b6b-b7ecb197fec6)
 *               [ReturnParameterMembership] Feature result (d6afa246-db68-40b8-af28-f8a685571415)
 *         [FeatureMembership] SuccessionAsUsage (9a2e8cad-f63c-4213-bc90-4e89ad961bfd)
 *           [Subsetting (implicit)] Feature happensBeforeLinks (0e1bba0a-81f0-518c-8415-d1976bd38f8d)
 *           [EndFeatureMembership] ReferenceUsage earlierOccurrence (cc9a1c4d-ad13-47fc-9fe5-930f6bbfd1a6)
 *             [Redefinition (implicit)] Feature earlierOccurrence (7d7065b6-1bb8-5bb5-b421-cc92f2e84584)
 *             [ReferenceSubsetting (implicit)] SendActionUsage (7b3d948b-163d-48a8-9245-162a3326c592)
 *             [OwningMembership] Multiplicity (c3b320f4-477c-4c2a-80d2-96bd7ff2b726)
 *               [Subsetting (implicit)] MultiplicityRange exactlyOne (64e18b84-0e05-5c95-a003-c0f60a269893)
 *           [EndFeatureMembership] ReferenceUsage laterOccurrence (af929f26-3546-4e1a-9b0f-9995b95f6393)
 *             [Redefinition (implicit)] Feature laterOccurrence (99bd4b60-e5a9-55fb-8cea-1dcf517e50ec)
 *             [ReferenceSubsetting] ActionUsage done (0cdc3cd3-b06c-5c32-beda-0cf4ba164a64)
 *             [OwningMembership] Multiplicity (1af8dae1-477b-41e6-af55-3b1b78bf66a6)
 *               [Subsetting (implicit)] MultiplicityRange exactlyOne (64e18b84-0e05-5c95-a003-c0f60a269893)
 *     [FeatureMembership] TransitionUsage (8163c4ab-7b90-4389-926a-c1fc6409bab9)
 *       [Subsetting (implicit)] ActionUsage stateTransitions (11737269-5f46-5232-8b0c-e70b7eec3b04)
 *       [Membership] StateUsage s1 (f39cbdc7-d20a-4ac3-9a31-cea2db848e76)
 *       [ParameterMembership] ReferenceUsage transitionLinkSource (c52662ca-6920-4bfa-b30a-f5dc97ba9aeb)
 *         [Redefinition (implicit)] ReferenceUsage transitionLinkSource (e9249917-217c-571c-8782-03609448f983)
 *       [ParameterMembership] ReferenceUsage payload (5e31d603-ffbc-4159-935d-3b0de3595a26)
 *         [Redefinition (implicit)] ReferenceUsage payload (30167df9-7f7b-5d9c-96c7-17889b6674c9)
 *         [Subsetting (implicit)] Feature accepter.payload (6b6a9059-b38f-4158-8d63-4e047bbd8f5a)
 *       [TransitionFeatureMembership] AcceptActionUsage accepter (94e5b553-8780-48f6-97ee-49a63a3ac434)
 *         [Redefinition (implicit)] ActionUsage accepter (2cdca507-48f3-5f52-ac1f-d8a7535d92c4)
 *         [ParameterMembership] ReferenceUsage payload (5d56bf99-dcbe-498c-86bb-75662b5ea48a)
 *           [Redefinition (implicit)] ReferenceUsage payload (780fbe59-dd70-56b5-bbd2-3d2f904daff3)
 *           [Subsetting (implicit)] Feature objects (33d1bd68-58e2-555e-98a3-b0b679542260)
 *           [FeatureTyping] ItemDefinition StateTransitionTrigger (bc4fa98a-3d9f-46b4-bfd3-975a27e7e852)
 *         [ParameterMembership] ReferenceUsage receiver (ef12f118-bf9c-4ec6-9470-ed38bde49949)
 *           [Redefinition (implicit)] Feature receiver (bce3ce09-e07f-5493-9ea6-fedc95de5fd4)
 *           [FeatureValue] FeatureReferenceExpression p1 (8bbac320-a61b-4f2b-b46c-239a30270a2b)
 *             [ReturnParameterMembership] Feature result (57a5cdbd-1fff-440d-9b17-65b29c41f06e)
 *       [OwningMembership] SuccessionAsUsage (86af64ca-4219-452b-81af-0061579f3db3)
 *         [Subsetting (implicit)] Feature happensBeforeLinks (0e1bba0a-81f0-518c-8415-d1976bd38f8d)
 *         [EndFeatureMembership] ReferenceUsage earlierOccurrence (06f8f606-e91c-4f65-aea3-1dc3f3490f1f)
 *           [Redefinition (implicit)] Feature earlierOccurrence (7d7065b6-1bb8-5bb5-b421-cc92f2e84584)
 *           [ReferenceSubsetting (implicit)] StateUsage s1 (f39cbdc7-d20a-4ac3-9a31-cea2db848e76)
 *           [OwningMembership] Multiplicity (09dc349d-334c-45ea-b9e1-33e12e36b666)
 *             [Subsetting (implicit)] MultiplicityRange exactlyOne (64e18b84-0e05-5c95-a003-c0f60a269893)
 *         [EndFeatureMembership] ReferenceUsage laterOccurrence (4d1df4ca-f4e4-48d0-bfa6-f86a1df1a293)
 *           [Redefinition (implicit)] Feature laterOccurrence (99bd4b60-e5a9-55fb-8cea-1dcf517e50ec)
 *           [ReferenceSubsetting] StateUsage s2 (dd414a42-348d-407d-a3fe-5eb0d81bbc4d)
 *           [OwningMembership] Multiplicity (81a5b44f-664f-4372-92e2-afd1ce26057d)
 *             [Subsetting (implicit)] MultiplicityRange exactlyOne (64e18b84-0e05-5c95-a003-c0f60a269893)
 *       [FeatureMembership] ReferenceUsage transitionLink (07308ffc-7313-44a2-949b-b0df99e8fcd9)
 *         [Redefinition (implicit)] Feature transitionLink (88fcc394-fccf-51de-a229-138dee74449e)
 *     [FeatureMembership] StateUsage s2 (dd414a42-348d-407d-a3fe-5eb0d81bbc4d)
 *       [Subsetting (implicit)] StateUsage exclusiveStates (127c2ef2-9f87-52f2-93f6-5f7acbbdb70b)
 *       [StateSubactionMembership] PerformActionUsage s2Do (c68b24e9-476c-4585-84f3-6e805f474481)
 *         [Redefinition (implicit)] PerformActionUsage doAction (be1e82ae-d5b8-53cf-8ae6-092905daf358)
 *         [FeatureMembership] AcceptActionUsage getDataFromS1 (08968010-8f7a-4aa8-a66b-cdf96ed50ff7)
 *           [Subsetting (implicit)] ActionUsage acceptSubactions (1f8424a7-2500-583d-a15a-494fbec0beef)
 *           [ParameterMembership] ReferenceUsage iFromS1 (19410970-9565-48df-98ae-f7edaad7e58a)
 *             [Redefinition (implicit)] ReferenceUsage payload (780fbe59-dd70-56b5-bbd2-3d2f904daff3)
 *             [Subsetting (implicit)] Feature objects (33d1bd68-58e2-555e-98a3-b0b679542260)
 *             [FeatureTyping] ItemDefinition I1 (f34d6b5b-010a-4d9f-8a4a-f4f2529d1815)
 *         [FeatureMembership] FlowUsage (17a41c24-9dd2-42a1-8c42-d814b3e4a0bb)
 *           [Subsetting (implicit)] FlowUsage flows (58f4b8ef-ef56-5e97-8def-549155818a37)
 *           [Subsetting (implicit)] ActionUsage subactions (3cd3b18a-02fd-5ca8-908a-9acac924a5b3)
 *           [EndFeatureMembership] FlowEnd source (286beedc-4ad7-400e-a2b6-a2b7b549600a)
 *             [Redefinition (implicit)] OccurrenceUsage source (9d174cd9-1d36-52f0-9c44-62001ffb9568)
 *             [ReferenceSubsetting] AcceptActionUsage getDataFromS1 (08968010-8f7a-4aa8-a66b-cdf96ed50ff7)
 *             [FeatureMembership] ReferenceUsage iFromS1 (5e4f1047-3e5f-4884-a8b4-d52f97c2dda7)
 *               [Redefinition (implicit)] Feature sourceOutput (b0828d4d-ca40-572c-8276-734daa226ea6)
 *               [Redefinition] ReferenceUsage iFromS1 (19410970-9565-48df-98ae-f7edaad7e58a)
 *           [EndFeatureMembership] FlowEnd target (7cc36ce7-405d-4763-943b-7af1ec800fe2)
 *             [Redefinition (implicit)] OccurrenceUsage target (bf43c516-b2fd-59b0-ae53-a534f1289406)
 *             [ReferenceSubsetting] PerformActionUsage a2 (18b839c8-36e0-4967-8cea-6f9b9eeb5390)
 *             [FeatureMembership] ReferenceUsage iin (1ddcb89f-26d8-4f54-8d5c-05cf2e941631)
 *               [Redefinition (implicit)] Feature targetInput (23f50cb6-e79a-5ea6-ab6f-6402cf94870b)
 *               [Redefinition] ItemUsage iin (b02e5d3f-91e0-4ec6-9141-de64d689e10a)
 *         [Membership] AcceptActionUsage getDataFromS1 (08968010-8f7a-4aa8-a66b-cdf96ed50ff7)
 *         [FeatureMembership] SuccessionAsUsage (46f60ed7-3852-4956-bd25-9ac040108c44)
 *           [Subsetting (implicit)] Feature happensBeforeLinks (0e1bba0a-81f0-518c-8415-d1976bd38f8d)
 *           [EndFeatureMembership] ReferenceUsage earlierOccurrence (28fa762e-94ae-4be7-96c0-ebc04e34feeb)
 *             [Redefinition (implicit)] Feature earlierOccurrence (7d7065b6-1bb8-5bb5-b421-cc92f2e84584)
 *             [ReferenceSubsetting (implicit)] AcceptActionUsage getDataFromS1 (08968010-8f7a-4aa8-a66b-cdf96ed50ff7)
 *             [OwningMembership] Multiplicity (5aacfeed-d26b-441b-8e37-fb6847907dae)
 *               [Subsetting (implicit)] MultiplicityRange exactlyOne (64e18b84-0e05-5c95-a003-c0f60a269893)
 *           [EndFeatureMembership] ReferenceUsage laterOccurrence (a7b73c15-34f2-484c-a979-3400425dd6d1)
 *             [Redefinition (implicit)] Feature laterOccurrence (99bd4b60-e5a9-55fb-8cea-1dcf517e50ec)
 *             [ReferenceSubsetting (implicit)] PerformActionUsage a2 (18b839c8-36e0-4967-8cea-6f9b9eeb5390)
 *             [OwningMembership] Multiplicity (2ca7dfb2-3e05-4118-8b9c-d4492312bb61)
 *               [Subsetting (implicit)] MultiplicityRange exactlyOne (64e18b84-0e05-5c95-a003-c0f60a269893)
 *         [FeatureMembership] PerformActionUsage a2 (18b839c8-36e0-4967-8cea-6f9b9eeb5390)
 *           [Subsetting (implicit)] Step enclosedPerformances (d2f2efc4-b3fe-5807-85bc-416fbebb05f0)
 *           [ReferenceSubsetting] PerformActionUsage a2 (96d92c9c-ee8b-4ab5-b32c-f771c5e3f5ab)
 *         [FeatureMembership] SuccessionAsUsage (98467a52-2e5e-47b1-9c6c-763562c920e2)
 *           [Subsetting (implicit)] Feature happensBeforeLinks (0e1bba0a-81f0-518c-8415-d1976bd38f8d)
 *           [EndFeatureMembership] ReferenceUsage earlierOccurrence (4ab41515-726b-4a01-a2a0-627866a0835d)
 *             [Redefinition (implicit)] Feature earlierOccurrence (7d7065b6-1bb8-5bb5-b421-cc92f2e84584)
 *             [ReferenceSubsetting (implicit)] PerformActionUsage a2 (18b839c8-36e0-4967-8cea-6f9b9eeb5390)
 *             [OwningMembership] Multiplicity (b06e295e-4d7b-437c-a340-d379a79f29ef)
 *               [Subsetting (implicit)] MultiplicityRange exactlyOne (64e18b84-0e05-5c95-a003-c0f60a269893)
 *           [EndFeatureMembership] ReferenceUsage laterOccurrence (3e923a36-a79f-4f3e-aa67-d8471da82e39)
 *             [Redefinition (implicit)] Feature laterOccurrence (99bd4b60-e5a9-55fb-8cea-1dcf517e50ec)
 *             [ReferenceSubsetting (implicit)] PerformActionUsage a3 (7f5d505c-a2fb-41de-8b9b-67847a14c035)
 *             [OwningMembership] Multiplicity (c303a5b4-d6f1-4802-8f03-d90b47e32320)
 *               [Subsetting (implicit)] MultiplicityRange exactlyOne (64e18b84-0e05-5c95-a003-c0f60a269893)
 *         [FeatureMembership] PerformActionUsage a3 (7f5d505c-a2fb-41de-8b9b-67847a14c035)
 *           [Subsetting (implicit)] Step enclosedPerformances (d2f2efc4-b3fe-5807-85bc-416fbebb05f0)
 *           [ReferenceSubsetting] PerformActionUsage a3 (fdf2cda8-560b-49f2-bbe9-df838c082f10)
 *         [FeatureMembership] SuccessionAsUsage (8cb04b04-9f90-497e-9701-366a830f6521)
 *           [Subsetting (implicit)] Feature happensBeforeLinks (0e1bba0a-81f0-518c-8415-d1976bd38f8d)
 *           [EndFeatureMembership] ReferenceUsage earlierOccurrence (df571210-bded-4ef4-ae0c-1466bd4543a7)
 *             [Redefinition (implicit)] Feature earlierOccurrence (7d7065b6-1bb8-5bb5-b421-cc92f2e84584)
 *             [ReferenceSubsetting (implicit)] PerformActionUsage a3 (7f5d505c-a2fb-41de-8b9b-67847a14c035)
 *             [OwningMembership] Multiplicity (5d8a44fb-4103-4c5c-bbb8-9bcdf3653499)
 *               [Subsetting (implicit)] MultiplicityRange exactlyOne (64e18b84-0e05-5c95-a003-c0f60a269893)
 *           [EndFeatureMembership] ReferenceUsage laterOccurrence (acc2a7f3-e378-43a9-aae9-5d49726daf96)
 *             [Redefinition (implicit)] Feature laterOccurrence (99bd4b60-e5a9-55fb-8cea-1dcf517e50ec)
 *             [ReferenceSubsetting] ActionUsage done (0cdc3cd3-b06c-5c32-beda-0cf4ba164a64)
 *             [OwningMembership] Multiplicity (bb9efb9e-5586-4c3e-9d8d-b77d875492bd)
 *               [Subsetting (implicit)] MultiplicityRange exactlyOne (64e18b84-0e05-5c95-a003-c0f60a269893)
 *     [FeatureMembership] TransitionUsage (df6ab533-3d34-4446-8b60-a0f4f9282903)
 *       [Subsetting (implicit)] ActionUsage stateTransitions (11737269-5f46-5232-8b0c-e70b7eec3b04)
 *       [Membership] StateUsage s2 (dd414a42-348d-407d-a3fe-5eb0d81bbc4d)
 *       [ParameterMembership] ReferenceUsage transitionLinkSource (098bf8bd-24a7-4504-b1cc-dec97ec8d2d1)
 *         [Redefinition (implicit)] ReferenceUsage transitionLinkSource (e9249917-217c-571c-8782-03609448f983)
 *       [OwningMembership] SuccessionAsUsage (ba0f2773-aa0b-46c2-9f95-0dca86bd8eac)
 *         [Subsetting (implicit)] Feature happensBeforeLinks (0e1bba0a-81f0-518c-8415-d1976bd38f8d)
 *         [EndFeatureMembership] ReferenceUsage earlierOccurrence (4338a37c-9c4c-4953-b6f8-734c71449f4f)
 *           [Redefinition (implicit)] Feature earlierOccurrence (7d7065b6-1bb8-5bb5-b421-cc92f2e84584)
 *           [ReferenceSubsetting (implicit)] StateUsage s2 (dd414a42-348d-407d-a3fe-5eb0d81bbc4d)
 *           [OwningMembership] Multiplicity (286e2ebd-8422-4d70-8bdd-48e3da8501c9)
 *             [Subsetting (implicit)] MultiplicityRange exactlyOne (64e18b84-0e05-5c95-a003-c0f60a269893)
 *         [EndFeatureMembership] ReferenceUsage laterOccurrence (5a27826d-e3a9-4c67-84b9-e6cf1686fdd9)
 *           [Redefinition (implicit)] Feature laterOccurrence (99bd4b60-e5a9-55fb-8cea-1dcf517e50ec)
 *           [ReferenceSubsetting] StateUsage done (c2229489-0c87-571f-806a-29ce5013452f)
 *           [OwningMembership] Multiplicity (e754aaf5-3402-4198-b388-de44a456e38e)
 *             [Subsetting (implicit)] MultiplicityRange exactlyOne (64e18b84-0e05-5c95-a003-c0f60a269893)
 *       [FeatureMembership] ReferenceUsage transitionLink (eb618fbb-1c97-4f30-94ee-1c8690a2daca)
 *         [Redefinition (implicit)] Feature transitionLink (88fcc394-fccf-51de-a229-138dee74449e)
 */
